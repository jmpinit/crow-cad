// Column order is: width, height, x, y

string commandBuffer = "";

void cmd(string cmdText) {
  string parts[] = { commandBuffer, cmdText };
  commandBuffer = strjoin(parts, ';');
}

string pinFilePath = dlgFileOpen("Select footprint dump file", "", "*.csv");

string lines[];
int lineCount = fileread(lines, pinFilePath);

for (int i = 0; i < lineCount; i++) {
  string columns[];
  int columnCount = strsplit(columns, lines[i], ',');

  if (columnCount != 4) {
    exit(EXIT_FAILURE);
  }

  // TODO somehow annotate Fusion 360 sketch with names?
  string name;
  sprintf(name, "%d", i);

  real width = strtod(columns[0]);
  real height = strtod(columns[1]);
  real x = strtod(columns[2]);
  real y = strtod(columns[3]);

  string smdCmd;
  sprintf(smdCmd, "SMD %f %f -0 '%s' (%f %f)", width, height, name, x, y);
  cmd(smdCmd);
}

exit(commandBuffer);
